[DOCUMENT]
TITLE: ROE Deploy Requirements
UID: DOC-DEPLOY
PREFIX: DEPLOY-

[TEXT]
STATEMENT: >>>
Behaviour of `make deploy PROJECT_NAME`, which applies the ROE template to a
sibling project, creating it if needed, without disturbing that project's own
files. ADR 006
recorded the original decision; these requirements state the properties it
must hold, checked against scripts/deploy-project.sh and the Makefile on
every `make test` via `make reqs-gate`.
<<<

[REQUIREMENT]
UID: DEPLOY-001
TITLE: Deploy targets adjacent project folders
STATEMENT: >>>
`make deploy PROJECT_NAME` shall resolve PROJECT_NAME as a directory that is
a sibling of the ROE repository (that is, in the parent of the ROE repository
root) and shall copy the ROE template into that directory.
<<<
RATIONALE: >>>
ADR 006: both repositories are directories under the same parent; this is
the invocation ROE deploy is built around. Implemented by the PROJECTS_DIR
and TARGET_DIR resolution in scripts/deploy-project.sh.
<<<

[REQUIREMENT]
UID: DEPLOY-002
TITLE: Deploy ships a template built from the current checkout
STATEMENT: >>>
`make deploy` shall regenerate tests/test-output/ROE_TEMPLATE_PROJECT from
the current checkout before every deployment, without a separate manual step
and without prompting.
<<<
RATIONALE: >>>
ADR 008. The original statement rebuilt the template only when it was
missing, so a template left by an earlier `make r` was deployed as-is: on
2026-10-25 that was ROE 1.0.0 from 2026-07-18. Implemented by the Makefile
`deploy` target's `template` prerequisite, ahead of
scripts/deploy-project.sh.
<<<

[REQUIREMENT]
UID: DEPLOY-003
TITLE: Deploy supports an empty destination folder
STATEMENT: >>>
`make deploy PROJECT_NAME` shall succeed when the destination sibling
directory already exists but is empty, copying the full template into it.
<<<
RATIONALE: >>>
Covers adopting ROE into a sibling project that was created but not yet
populated. Verified by tests/test-deploy.sh, which deploys into a freshly
created empty directory.
<<<

[REQUIREMENT]
UID: DEPLOY-004
TITLE: Deploy never overwrites existing destination files
STATEMENT: >>>
`make deploy` shall not overwrite any file that already exists in the
destination directory. Only files absent from the destination shall be
written.
<<<
RATIONALE: >>>
SAFETY-tier: deploying into a live sibling project must never destroy that
project's own work. Implemented with `cp -an` (no-clobber) in
scripts/deploy-project.sh. Verified by tests/test-deploy.sh, which asserts a
pre-existing README.md survives deployment unchanged.
<<<

[REQUIREMENT]
UID: DEPLOY-005
TITLE: Deploy creates a missing destination folder
STATEMENT: >>>
When the destination sibling directory does not exist, `make deploy
PROJECT_NAME` shall create it and then copy the full template into it.
PROJECT_NAME shall be a plain directory name; a name containing `/`, or
equal to `.` or `..`, shall be rejected.
<<<
RATIONALE: >>>
Requested so a new project can be started with one command, without a
separate `mkdir`. Revises ADR 006, which originally required the destination
to exist. The plain-name check keeps creation inside the parent of the ROE
repository, as DEPLOY-001 requires. Verified by tests/test-deploy.sh, which
deploys to a sibling name that does not exist yet.
<<<
